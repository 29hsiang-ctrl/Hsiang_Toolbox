;;; acaddoc.lsp - Hsiang_Toolbox auto startup

(defun s::startup ()
  (princ "\n==============================================")
  (princ "\n   Hsiang_Toolbox starting...")
  (princ "\n==============================================")
  (Hsiang_AutoLoader)
  (Hsiang_LoadMenu)
  (princ "\n")
)

(defun Hsiang_AutoLoader (/ path files file loadedCount)
  (vl-load-com)
  (setq path "C:\\Hsiang_Toolbox\\autocad-Lisp\\Lisp\\")
  (setq loadedCount 0)
  (setq files (vl-directory-files path "*.lsp" 1))
  (if files
    (foreach file files
      (princ (strcat "\n[Load] " file " ...... "))
      (if (load (strcat path file) nil)
        (progn
          (princ "OK!")
          (setq loadedCount (1+ loadedCount))
        )
        (princ "Error!")
      )
    )
    (princ "\n[Warning] No .lsp files found in Lisp folder!")
  )
  (princ (strcat "\n----------------------------------------------"))
  (princ (strcat "\n[Done] Loaded " (itoa loadedCount) " files. Commands: CT, LL, LX, SD, NN, T, SLT, DL, DC, DE, LD, SCD, UP, CNT"))
  (princ "\n==============================================")
  (princ)
)

(defun Hsiang_LoadMenu (/ basePath menuPath cuixPath)
  (setq basePath "C:\\Hsiang_Toolbox\\autocad-Lisp")
  (setq menuPath (strcat basePath "\\Menu\\Hsiang_Menu.mnu"))
  (setq cuixPath (strcat basePath "\\Menu\\Hsiang_Menu.cuix"))
  (setvar "MENUBAR" 1)
  (if (not (menugroup "HSIANG_TOOLS"))
    (cond
      ((findfile cuixPath)
       (command "_.MENULOAD" cuixPath)
       (princ "\n[Menu] Hsiang menu loaded from .cuix")
      )
      ((findfile menuPath)
       (command "_.MENULOAD" menuPath)
       (princ "\n[Menu] Hsiang menu loaded from .mnu")
      )
      (t (princ "\n[Warning] Menu file not found! Run HsiangInstall to set up."))
    )
    (princ "\n[Menu] Hsiang menu already loaded.")
  )
  (Hsiang_AddToMenuBar)
  (princ)
)

(defun Hsiang_AddToMenuBar (/ acadObj groups hsiangGroup menus popup menuBar)
  (vl-load-com)
  (if (menugroup "HSIANG_TOOLS")
    (progn
      (setq acadObj     (vlax-get-acad-object))
      (setq groups      (vla-get-MenuGroups acadObj))
      (setq hsiangGroup (vla-item groups "HSIANG_TOOLS"))
      (setq menus       (vla-get-Menus hsiangGroup))
      (setq popup       (vla-item menus 0))
      (if (not (= :vlax-true (vla-get-OnMenuBar popup)))
        (progn
          (setq menuBar (vla-get-MenuBar acadObj))
          (vla-InsertInMenuBar popup (vla-get-Count menuBar))
          (princ "\n[Menu] Hsiang工具 已加入傳統選單列")
        )
      )
    )
  )
  (princ)
)

;; Run immediately on first load (before any drawing opens)
(Hsiang_AutoLoader)
